RPKI-ROA-2022 { iso(1) member-body(2) us(840) rsadsi(113549)
  pkcs(1) pkcs9(9) smime(16) mod(0) id-mod-rpkiROA-2022(TBD) }

DEFINITIONS EXPLICIT TAGS ::=
BEGIN

IMPORTS
  CONTENT-TYPE
  FROM CryptographicMessageSyntax-2010 -- in [RFC6268]
    { iso(1) member-body(2) us(840) rsadsi(113549) pkcs(1)
      pkcs-9(9) smime(16) modules(0) id-mod-cms-2009(58) } ;

ct-routeOriginAttestation CONTENT-TYPE ::=
  { TYPE RouteOriginAttestation
    IDENTIFIED BY id-ct-routeOriginAuthz }

id-ct-routeOriginAuthz OBJECT IDENTIFIER ::=
  { iso(1) member-body(2) us(840) rsadsi(113549) pkcs(1)
    pkcs-9(9) id-smime(16) id-ct(1) routeOriginAuthz(24) }

RouteOriginAttestation ::= SEQUENCE {
  version [0]           INTEGER DEFAULT 0,
  asID                  ASID,
  ipAddrBlocks          SEQUENCE (SIZE(1..2)) OF ROAIPAddressFamily }

ASID ::= INTEGER (0..4294967295)

-- addressFamily must be '0001'H (IPv4) or '0002'H (IPv6). --
ROAIPAddressFamily ::= SEQUENCE {
  addressFamily         OCTET STRING (SIZE(2)),
  addresses             SEQUENCE (SIZE(1..MAX)) OF ROAIPAddress }

-- maxLength must be greater than or equal to the size of IPAddress, --
-- and smaller than or equal to what the AFI context permits.        --
ROAIPAddress ::= SEQUENCE {
  address               IPAddress,
  maxLength             INTEGER (0..128) OPTIONAL }

-- If the ROAIPAddressFamily's addressFamily is IPv4, the size of --
-- the IPAddress cannot exceed 32. If addressFamily is IPv6, the  --
-- size cannot exceed 128.                                        --
IPAddress ::= BIT STRING (SIZE(0..128))

END
